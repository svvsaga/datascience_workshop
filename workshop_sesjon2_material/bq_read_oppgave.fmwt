FME workspace bq_read_oppgave.fmwt
Title: feat

Parameters:
- SourceDataset_GEOJSON = https://github.com/smistad/konverter-norgeskart-projeksjon/releases/download/v2020/kommuner_komprimert.json   # Source GeoJSON File or URL
- DestDataset_CSV2 = C:\Users\gunsch\Documents\FME\Workspaces   # Destination CSV (Comma Separated Value) Folder
- GEOJSON_File =   # Destination GeoJSON File

Readers:
- GEOJSON_1: GEOJSON from $(SourceDataset_GEOJSON) in LL84

Writers:
- CSV2_1: CSV2 to $(DestDataset_CSV2)
- GEOJSON_2: GEOJSON to $(GEOJSON_File)

Note: BigQuery read workflow: / - Kjær en spørring i BigQuery / - Skriv resultatene til en GeoJSON fil
Note: Lag en Creator transformer som input til GoogleBigQueryConnector
Note: Kjør en spørring i BigQuery / - Bruk GoogleBigQueryConnector / - BigQueryConnector trenger en gyldig web-connection / - vil vil hente kommunenavn, gjennomsnittlig trafikkvolumen per kommune i 2019 og kommunegeografi
Note: < GoogleBigQueryConnector >
Creator
    GEOMTYPE = Geometry Object
    NUM = 1
Note: Skriv resultatene f.eks til en GeoJSON fil (Bruk GeoJSON writer) / - skriv kommunenavn, gjennomsnittlig volumen og kommunegeografi til fil
Write GeoJSON (writer GEOJSON_2)
    attributes: kommunenavn string, avg_volume string, geometry string
