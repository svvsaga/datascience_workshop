FME workspace bq_write_oppgave.fmw
Title: bq_write

Parameters:
- SourceDataset_GEOJSON = https://github.com/smistad/konverter-norgeskart-projeksjon/releases/download/v2020/kommuner_komprimert.json   # Source GeoJSON File or URL
- DestDataset_GEOJSON = $(FME_MF_DIR)bq_write_oppgave/kommuner.geojson   # Destination GeoJSON File
- BigQuery_connection =   # "safe.google-bigquery.Google BigQuery" Account
- BigQuery_project =   # project_name
- BigQuery_dataset = workshop   # dataset_name
- BigQuery_table = kommune   # table_name

Readers:
- GEOJSON_1: GEOJSON from $(SourceDataset_GEOJSON) in LL84

Writers:
- SAFE.GOOGLE-BIGQUERY.GOOGLEBIGQUERY_1: SAFE.GOOGLE-BIGQUERY.GOOGLEBIGQUERY
- GEOJSON_2: GEOJSON to $(DestDataset_GEOJSON)

Note: (1) Konfigurer GEOJson reader: / - legge til en GEOJson reader / - konfigurer readern: / - som kildefil set url = https://github.com/smistad/konverter-norgeskart- projeksjon/releases/download/v2020/kommuner_komprimert.json / - la alt annet stå som default
Note: (0) Konfigurer en web connection til BigQuery / - velg Tools -> FME options -> Web connections -> "+" -> "GoogleBigQuery (safe.GoogleBigQuery)" / - Trykk på "authenticate" og går gjennom interaktive oAuth2 autentisering (krever GCP bruker + passord)
Note: (2) Konfigurer en GEOJson writer / - legge til en GEOJson writer / - konfigurer den slik at den leser fra GEOJson reader og skriver feltene til en lokal fil. / - ser på filformat / -Rediger "User attributes" / - velg "Attribute Definition" -> Manual / - legg til et ny felt med navn "kommune" og konfigurer "value" til navn{0}.navn
kommuner_komprimert (reader GEOJSON_1)
    attributes: kommunenummer string, objtype string, lokalid string, oppdateringsdato string, datauttaksdato string, versjonid string, opphav string, samiskforvaltningsomrade boolean, datafangstdato string, navnerom string, navn{}.rekkefolge string, navn{}.sprak string, navn{}.navn string
    -> GeoJSON writer (writer GEOJSON_2)
    -> kommuner_from_url (writer SAFE.GOOGLE-BIGQUERY.GOOGLEBIGQUERY_1)
Note: (3) Konfigurer BigQuery writer / - legg til en GoogleBigQueryWriter / - Konfigurer "Service connection" til å bruke "Web connection" og velg connection du lagde i (0) / - IKKE sett en verdi i "coordinate system" / - videre konfigurere ved å velge ditt workshop prosjekt / - sette opp destinasjons datasett og tabell (velg "workshop" som datasett og "kommuner" som tabellnavn) / - Koble output fra GEOJson reader til BigQueryWriter / - Kjør workflowen / - Utforsk destinasjons tabellen i BigQuery's brukergrensesnitt (nettleser)
kommuner_from_url (writer SAFE.GOOGLE-BIGQUERY.GOOGLEBIGQUERY_1)
    attributes: kommunenummer STRING, objtype STRING, lokalid STRING, oppdateringsdato STRING, datauttaksdato STRING, versjonid STRING, opphav STRING, samiskforvaltningsomrade BOOLEAN, datafangstdato STRING, navnerom STRING, kommune STRING
GeoJSON writer (writer GEOJSON_2)
    attributes: kommunenummer string, objtype string, lokalid string, oppdateringsdato string, datauttaksdato string, versjonid string, opphav string, samiskforvaltningsomrade boolean, datafangstdato string, navnerom string, navn{}.rekkefolge string, navn{}.sprak string, navn{}.navn string, kommune string
