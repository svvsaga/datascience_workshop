FME workspace NVDBapi_kommune.fmwt
Title: NONE to SAFE.GOOGLE-BIGQUERY.GOOGLEBIGQUERY

Parameters:
- BigQuery_project =
- BigQuery_webconnection =

Writers:
- SAFE.GOOGLE-BIGQUERY.GOOGLEBIGQUERY_1: SAFE.GOOGLE-BIGQUERY.GOOGLEBIGQUERY

Creator
    GEOMTYPE = Geometry Object
    NUM = 1
    CREATED -> AttributeCreator
AttributeCreator
    ATTR_TABLE = SET_TO hentdataURL = https://nvdbapiles-v3.atlas.vegvesen.no/vegobjekter/946?segmentering=true&inkludergeometri=utledet&start=y24ZxsYwUStLit7FxV4EyLthj5hZwBjtmkysxhwFNko2usSVKEeuZGKERf6LBKMSHpNTg14pzGE24SXcazdiwVUJpYGXzWLe3n&inkluder=metadata%2Cegenskaper%2Cgeometri&srid=wgs84
    -> paginering_segmentertvegnett [HTTPCaller_Input]
paginering_segmentertvegnett: PagineringNvdbApiKommuner
    HENTDATAURL = @Value(hentdataURL)
    HTTPCaller_Output -> JSONFragmenter
JSONFragmenter
    EXPLODE_FORMAT = JSON
    EXTRACT_ATTR = Yes
    JSON_ATTR = _response_body
    JSON_QUERY = json["objekter"][*]
    READ_FROM_FILE = NO
    RECURSIVE = No
    REJECT_EMPTY_LISTS = YES
    FRAGMENTS -> JSONExtractor
JSONExtractor
    EXTRACT_QUERY_TABLE = egenskaper json["egenskaper"] geometri json["geometri"]["wkt"]
    JSON_DOCUMENT = @Value(_response_body)
    READ_FROM_FILE = NO
    EVALUATED -> JSONExtractor_2
JSONExtractor_2
    EXTRACT_QUERY_TABLE = kommunenummer json[0]["verdi"] kommunenavn json[1]["verdi"]
    JSON_DOCUMENT = @Value(egenskaper)
    READ_FROM_FILE = NO
    EVALUATED -> GeometryReplacer
GeometryReplacer
    KIND_LONG = OGC Well Known Text
    OGC_WKT_PRECISION_DISPLAY = 64-bit
    REMOVE_ATTRIBUTE = Yes
    SOURCE = @Value(geometri)
    -> CoordinateSystemSetter
CoordinateSystemSetter
    COORDSYS = LL-WGS84
    -> CoordinateSwapper
CoordinateSwapper
    SWAP_TYPE = X <-> Y
    -> Table7 (writer SAFE.GOOGLE-BIGQUERY.GOOGLEBIGQUERY_1)
Table7 (writer SAFE.GOOGLE-BIGQUERY.GOOGLEBIGQUERY_1)
    attributes: kommunenavn STRING, kommunenummer STRING

FME custom transformer PagineringNvdbApiKommuner

Parameters:
- HENTDATAURL =

HTTPCaller_Input (input)
    -> HTTPCaller
HTTPCaller_Output (output)
HTTPCaller_Input (output)
Tester_Failed (output)

Bookmark: paginering
HTTPCaller
    CONNECTION_TIMEOUT_LENGTH = 60
    CUSTOM_HEADERS = Accept;application/json X-Client;Saga
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = @Value(hentdataURL)
    TRANSFER_TIMEOUT_LENGTH = 90
    USE_COOKIES = No
    VERIFY_SSL_CERTIFICATES = Yes
    -> JSONFragmenter_2
    -> HTTPCaller_Output (output)
    <REJECTED> -> HTTPCaller__Rejected_
HTTPCaller__Rejected_: Inspector
JSONFragmenter_2
    EXPLODE_FORMAT = JSON
    EXTRACT_ATTR = Yes
    JSON_ATTR = _response_body
    JSON_QUERY = json["metadata"]
    NEW_ATTRIBUTES = neste.start neste.href antall returnert
    READ_FROM_FILE = NO
    RECURSIVE = Yes
    REJECT_EMPTY_LISTS = YES
    FRAGMENTS -> Tester
Tester
    BOOL_OP = OR
    COMPOSITE_TEST = 1
    TEST_CLAUSE = TEST @Value(returnert) > 0
    TEST_MODE = TEST
    PASSED -> AttributeCreator_2
    FAILED -> Tester_Failed (output)
AttributeCreator_2
    ATTR_TABLE = SET_TO hentdataURL = @Value(neste.href)
    -> HTTPCaller_Input (output)
