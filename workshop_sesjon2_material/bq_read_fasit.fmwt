FME workspace bq_read_fasit.fmwt
Title: feat

Parameters:
- SourceDataset_GEOJSON = https://github.com/smistad/konverter-norgeskart-projeksjon/releases/download/v2020/kommuner_komprimert.json   # Source GeoJSON File or URL
- DestDataset_CSV2 = C:\Users\gunsch\Documents\FME\Workspaces   # Destination CSV (Comma Separated Value) Folder
- GEOJSON_File =   # Destination GeoJSON File
- __googlebigquery_connection =   # "safe.google-bigquery.Google BigQuery"% Account
- __googlebigquery_project_id =

Readers:
- GEOJSON_1: GEOJSON from $(SourceDataset_GEOJSON) in LL84

Writers:
- CSV2_1: CSV2 to $(DestDataset_CSV2)
- GEOJSON_2: GEOJSON to $(GEOJSON_File)

Note: BigQuery read workflow: / - Kjær en spørring i BigQuery / - Skriv resultatene til en GeoJSON fil
Note: Lag en Creator transformer som input til GoogleBigQueryConnector
Creator
    GEOMTYPE = Geometry Object
    NUM = 1
    CREATED -> GoogleBigQueryConnecto
Note: Kjør en spørring i BigQuery / - Bruk GoogleBigQueryConnector / - BigQueryConnector trenger en gyldig web-connection / - vil vil hente kommunenavn, gjennomsnittlig trafikkvolumen per kommune i 2019 og kommunegeografi
GoogleBigQueryConnecto: GoogleBigQueryConnector
    __googlebigquery_action = Query
    __googlebigquery_action_options:
      __googlebigquery_query[SELECT
        kommunenavn,
        AVG(volume) avg_volume,
        ANY_VALUE(geometry) geometry
      FROM
        `saga-workshop-data-vu8x.workshop.produksjonstabell`
      WHERE
        startOfHour BETWEEN "2019-01-01"
        AND "2019-12-31"
      GROUP BY
        1[__googlebigquery_enable_dest[NO[__googlebigquery_dest_table[<Unused>[__googlebigquery_dest_method[<Unused>[__googlebigquery_dest_dataset[<Unused>[__googlebigquery_attributes_to_add["kommunenavn avg_volume geometry"[__googlebigquery_geometry_attributes_to_add[geometry[FME_CONTROLLER_QUERY_FILE[bq_deps/Query.fme
    __googlebigquery_connection = $(__googlebigquery_connection)
    __googlebigquery_credential_source = WEBCONN
    __googlebigquery_project_id = $(__googlebigquery_project_id)
    -> Write GeoJSON (writer GEOJSON_2)
Note: Skriv resultatene f.eks til en GeoJSON fil (Bruk GeoJSON writer) / - skriv kommunenavn, gjennomsnittlig volumen og kommunegeografi til fil
Write GeoJSON (writer GEOJSON_2)
    attributes: kommunenavn string, avg_volume string, geometry string
