FME workspace bq_readwrite_oppgave.fmwt
Title: feat

Parameters:
- DestDataset_CSV2 =
- SourceDataset_GEOJSON =
- __googlebigquery_connection =
- __googlebigquery_project_id =
- gbq_dest_dataset =
- gbq_dest_table =

Readers:
- GEOJSON_1: GEOJSON from $(SourceDataset_GEOJSON) in LL84

Writers:
- CSV2_1: CSV2 to $(DestDataset_CSV2)
- SAFE.GOOGLE-BIGQUERY.GOOGLEBIGQUERY_1: SAFE.GOOGLE-BIGQUERY.GOOGLEBIGQUERY

Note: Pivot table workflow: / - Kjør en spørring i BigQuery som aggregerer total trafikkvolumen per trpId og ukedag / - Bruk en AttributePivoter til å endre tabell format slik at hver ukedag får en egen kolonne
Note: BigQuery spørring / - Bruk GoogleBigQueryConnector til å kjøre en aggregasjonsspørring / - Husk å eksponere relevante kolonner
Note: < GoogleBigQUeryConnector>
Creator
    GEOMTYPE = Geometry Object
    NUM = 1
Note: Lag en pivot tabell med trpId (rader) ganger ukedager (kolonner) / - bruk av AttributePivoter transformer
Note: < AttributePivoter r>
Note: Eksponer nye attributer (ukedager kolonner) / - Bruk AttributExposer
AttributeExposer
    ATTR_LIST = 1,2,3,4,5,6,7
    -> fme_pivot_ukedager (writer SAFE.GOOGLE-BIGQUERY.GOOGLEBIGQUERY_1)
Note: Skriv til BigQuery / - Bruk BigQueryWriter
fme_pivot_ukedager (writer SAFE.GOOGLE-BIGQUERY.GOOGLEBIGQUERY_1)
    attributes: trpId STRING, Sunday FLOAT64, Monday FLOAT64, Tuesday FLOAT64, Wednesday FLOAT64, Thursday FLOAT64, Friday FLOAT64, Saturday FLOAT64
