FME workspace bq_readwrite_fasit.fmwt
Title: feat

Parameters:
- DestDataset_CSV2 =
- SourceDataset_GEOJSON =
- __googlebigquery_connection =
- __googlebigquery_project_id =
- gbq_dest_dataset =
- gbq_dest_table =

Readers:
- GEOJSON_1: GEOJSON from $(SourceDataset_GEOJSON) in LL84

Writers:
- CSV2_1: CSV2 to $(DestDataset_CSV2)
- SAFE.GOOGLE-BIGQUERY.GOOGLEBIGQUERY_1: SAFE.GOOGLE-BIGQUERY.GOOGLEBIGQUERY

Note: Pivot table workflow: / - Kjør en spørring i BigQuery som aggregerer total trafikkvolumen per trpId og ukedag / - Bruk en AttributePivoter til å endre tabell format slik at hver ukedag får en egen kolonne
Creator
    GEOMTYPE = Geometry Object
    NUM = 1
    CREATED -> GoogleBigQueryConnector
Note: BigQuery spørring / - Bruk GoogleBigQueryConnector til å kjøre en aggregasjonsspørring / - Husk å eksponere relevante kolonner
GoogleBigQueryConnector
    __googlebigquery_action = Query
    __googlebigquery_action_options:
      __googlebigquery_query[SELECT
        trpId,
        EXTRACT(DAYOFWEEK
        FROM
          lokaltid) ukedag,
        AVG(volume) volumen
      FROM
        `saga-workshop-data-vu8x.workshop.produksjonstabell`
      GROUP BY
        1,
        2[__googlebigquery_enable_dest[NO[__googlebigquery_dest_table[<Unused>[__googlebigquery_dest_method[<Unused>[__googlebigquery_dest_dataset[<Unused>[__googlebigquery_attributes_to_add["trpId ukedag volumen"[__googlebigquery_geometry_attributes_to_add[[FME_CONTROLLER_QUERY_FILE[bq_deps/Query.fme
    __googlebigquery_connection = $(__googlebigquery_connection)
    __googlebigquery_credential_source = WEBCONN
    __googlebigquery_project_id = $(__googlebigquery_project_id)
    -> AttributePivoter
Note: Lag en pivot tabell med trpId (rader) ganger ukedager (kolonner) / - bruk av AttributePivoter transformer
AttributePivoter
    COLUMN_GROUP_ATTR = ukedag
    GROUP_TOTALS_TAG = Total
    INCLUDE_GRAND_TOTALS = No
    PIVOT_ATTR = volumen
    PIVOT_SUMMARY_TYPES = Average
    ROW_GROUP_ATTRS = trpId
    DATA -> AttributeExposer
Note: Eksponer nye attributer (ukedager kolonner) / - Bruk AttributExposer
AttributeExposer
    ATTR_LIST = 1,2,3,4,5,6,7
    -> fme_pivot_ukedager (writer SAFE.GOOGLE-BIGQUERY.GOOGLEBIGQUERY_1)
Note: Skriv til BigQuery / - Bruk BigQueryWriter
fme_pivot_ukedager (writer SAFE.GOOGLE-BIGQUERY.GOOGLEBIGQUERY_1)
    attributes: trpId STRING, Sunday FLOAT64, Monday FLOAT64, Tuesday FLOAT64, Wednesday FLOAT64, Thursday FLOAT64, Friday FLOAT64, Saturday FLOAT64
