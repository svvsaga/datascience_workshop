FME workspace bq_write_oppgave.fmwt
Title: bq_write

Parameters:
- BigQuery_connection =
- BigQuery_dataset =
- BigQuery_project =
- BigQuery_table =
- GCS_bucket =
- GCS_connector =
- Lokal_GeoJSON_fil =
- Source_URL =

Readers:
- GEOJSON_1: GEOJSON from $(Source_URL) in LL84

Note: Kort om denne oppgaven: / - Det vi skal gjøre er å laste ned et datasett som inneholder norske kommuner og deres kommunegrenser, for så å skrive dette til en lokal fil, laste opp fila til GCS, samt importere kommunene til BigQuery / - Oppgavene står i gule lapper ala den du leser nå / - For å spare tid har vi allerede lagt inn løsning for de fleste oppgaver. Du bør likevel lese gjennom oppgavene for å forstå hvordan workflowen henger sammen. / - Du må selv utføre oppgave 0 og 3 / - I prosjektet ditt finnes det allerede en bøtte ved navn "saga-workshop-<ditt_kortnavn>-fme-bucket" som dere skal bruke som GCS-bøtte her
Note: (0) Konfigurer en web connection til BigQuery og Cloud Storage / - velg Tools -> FME options -> Web connections -> "+" -> "GoogleBigQuery (safe.GoogleBigQuery)" / - Trykk på "authenticate" og går gjennom interaktive oAuth2 autentisering (krever GCP bruker + passord) / - Gjør det samme til å opprette og konfigurere en GoogleCloudStorage connection
Note: (1) Konfigurer GeoJSON reader: / - legge til en GeoJSON reader / - konfigurer readeren: / - som kildefil set url = https://github.com/smistad/konverter-norgeskart- projeksjon/releases/download/v2020/kommuner_komprimert.json / - la alt annet stå som default
kommuner_komprimert (reader GEOJSON_1)
    attributes: kommunenummer string, objtype string, lokalid string, oppdateringsdato string, datauttaksdato string, versjonid string, opphav string, samiskforvaltningsomrade boolean, datafangstdato string, navnerom string, navn{}.rekkefolge string, navn{}.sprak string, navn{}.navn string
    -> ListIndexer:_0
Note: Kommunedatasettet kan inneholde en liste med både samisk og norsk kommunenavn. Uheldigvis klarer ikke GoogleBigQueryWriter å skrive lister eller nøstede strukturer til BigQuery, selv om BigQuery støtter det. Derfor bruker vi her ListIndexer og AttributeKeeper for å plukke ut det norske kommunenavnet.
Note: (2) Konfigurer en FeatureWriter i GEOJson format, som lagrer fil lokalt / - bruk GeoJSON reader som input / - bruk default verdiene i konfigurasjon
ListIndexer:_0
    INDEX = 0
    LIST_ATTR = navn{}
    -> AttributeKeeper
Note: (3) Konfigurer BigQuery writer / - legg til en GoogleBigQueryWriter ved å trykke på "Add writer" og finne frem "Google BigQuery" under "More formats" i "Formats"-boksen / - Gå så inn på "parameters" / - Konfigurer "Service connection" til å bruke "Web connection" og velg connection du lagde i (0) / - Velg også workshop-prosjektet du har fått utdelt, samt "workshop"-datasettet du lagde i sesjon 1. / - Velg spatial type = "Geography" og skriv inn at kolonnenavnet skal være "geometry" / - Trykk OK for å gå ut av "parameters" / - IKKE sett en verdi i "coordinate system" / - La "Table definition" være "Automatic". Trykk OK. / - Når du blir spurt om det, velg tabellnavn, f.eks. "kommuner", og trykk OK. / - Koble outputten fra AttributeKeeper til input på BigQueryWriter-en som du akkurat lagde / - Verifiser at modulen nå har fått synlige attributter som "kommunenummer" og "navn" / - Kjør workflowen / - Utforsk destinasjonstabellen i BigQuery's brukergrensesnitt (nettleser)
Note: Plasser din <GoogleBigQueryWriter> under her
AttributeKeeper
    CREATE_BULK_MODE_FEATURES = NO
    KEEP_ATTRS = datafangstdato,datauttaksdato,kommunenummer,lokalid,navn,navnerom,objtype,oppdateringsdato,opphav,samiskforvaltningsomrade
    -> FeatureWriter [kommuner_komprimert]
FeatureWriter
    DATASET = $(Lokal_GeoJSON_fil)
    DATASET_ATTR = _dataset
    FEATURE_TYPE_LIST_ATTR = _feature_type
    FORMAT = GEOJSON
    GEOJSON_COUNTER_CLOCKWISE_AREAS = Yes
    GEOJSON_DESTINATION_DATASETTYPE_VALIDATION = Yes
    GEOJSON_FILE_STRUCTURE = SINGLE_FEATURE_COLLECTION
    GEOJSON_INDENT_SIZE = 0
    GEOJSON_MAX_COORDINATE_PRECISION = 10
    GEOJSON_PRETTY_PRINT = YES
    GEOJSON_WGS84_REPROJECTION = Yes
    GEOJSON_WRITER_CHARSET = UTF-8
    GEOJSON_WRITE_BOM = No
    SELECTED_PORTS = kommuner_komprimert
    TOTAL_FEATURES_WRITTEN_ATTR = _total_features_written
    SUMMARY -> GoogleCloudStorageConnector
Note: (4) Bruk GoogleCloudStorageConnector til å lese en lokal fil og laste opp till en GCS bucket / - google cloud storage trenger sin egen web-connection til autentisering / - koble summary fra FeatureWriter som input til StorageConnector
GoogleCloudStorageConnector
    CREDENTIAL_SOURCE = WEBCONN
    OPERATION_TYPE = Upload
    PARAMETER_SETUP = _FME_SOURCE_TYPE]File]_FME_SOURCE_FILE]$(Lokal_GeoJSON_fil)]_FME_SOURCE_FOLDER]<Unused>]_FME_INCLUDE_SUBFOLDERS]<Unused>]_FME_CONTENTS_ONLY]<Unused>]_FME_DATA_TO_UPLOAD]<Unused>]_FME_BUCKET]$(GCS_bucket)]_FME_UPLOAD_DESTINATION_PATH]/]_FME_UPLOAD_ATTR_FILENAME]<Unused>]_FME_HANDLE_EXISTING_FILE]Overwrite]_FME_GCS_ACL]private]_FME_METADATA_GROUP]FME_DISCLOSURE_CLOSED]_FME_CUSTOM_HEADERS]]_FME_ATTRIBUTES_TO_ADD]"_url _name _full_path _bucket"]FME_CONTROLLER_QUERY_FILE]googlecloudstorageconnector_deps/Upload.fme]FME_CONTROLLER_CHOICE]Upload
    _FME_PROJECT_ID = $(BigQuery_project)
    __googlecloudstorageconnector_connection = $(GCS_connector)
